FME workspace data_processing.fmw

Parameters:
- source_id = pbghis8kc
- url = https://enacit4r-cdn.epfl.ch/EIRA/2023-01-20

Creator_3 [off]
    GEOMTYPE = Geometry Object
    NUM = 1
    CREATED -> FeatureReader_12 [INITIATOR] [off]
    CREATED -> FeatureReader_13 [INITIATOR] [off]
    CREATED -> FeatureReader_14 [INITIATOR] [off]
FeatureReader_14 [off]
    ATTRIBUTES = GEOTIFF,
    ATTR_ACCUM_MODE = Only Use Result
    COMBINE_GEOM = Use Result
    DATASET = C:\projects\EIRA-data\Data\Piezometer Analysis\01-Basefiles\Topography\hillshade.tif
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = NONE
    OUTPUT_FEATURES_DISPLAY = Schema and Data Features
    GEOTIFF -> AttributeExposer_8 [off]
AttributeExposer_8 [off]
    ATTR_LIST = fme_dataset
    -> StringReplacer_8 [off]
StringReplacer_8 [off]
    CASE = NO
    FIND_TEXT = C:\projects\EIRA-data\Data\Piezometer Analysis\01-Basefiles\Topography\
    NO_MATCH = _FME_NO_OP_
    REGEXP = NO
    SRC_ATTRS = fme_dataset
    -> StringReplacer_9 [off]
StringReplacer_9 [off]
    CASE = NO
    FIND_TEXT = _raster_edit
    NO_MATCH = _FME_NO_OP_
    REGEXP = NO
    SRC_ATTRS = fme_dataset
    -> StringReplacer_10 [off]
StringReplacer_10 [off]
    CASE = NO
    FIND_TEXT = .tif
    NO_MATCH = _FME_NO_OP_
    REGEXP = NO
    SRC_ATTRS = fme_dataset
    -> WebMapTiler_3 [off]
    -> AttributeCreator_9 [off]
    -> AttributeCreator_10 [off]
WebMapTiler_3 [off]
    INTERPOLATION_TYPE_NAME = Nearest Neighbor
    MAX_ZOOM_LEVEL = 14
    MIN_ZOOM_LEVEL = 1
    NUM_TILES_ATTRIBUTE = _num_tiles
    QUADKEY_ATTRIBUTE = _quadkey
    RASTER_INDEX_ATTRIBUTE = _raster_index
    TILE_COLUMN_ATTRIBUTE = _tile_column
    TILE_ROW_ATTRIBUTE = _tile_row
    TILE_SCHEME = GoogleMapsCompatible
    ZOOM_LEVEL_ATTRIBUTE = _zoom_level
    TILES -> FeatureWriter_16 [Output] [off]
FeatureWriter_16 [off]
    DATASET = C:\projects\EIRA-data\Data\raster_output\topo_hillshade\@Value(_zoom_level)\@Value(_tile_column)
    DATASET_ATTR = _dataset
    FEATURE_TYPE_LIST_ATTR = _feature_types
    FORMAT = PNGRASTER
    PNGRASTER_COORDINATE_SYSTEM_GRANULARITY = FEATURE
    TOTAL_FEATURES_WRITTEN_ATTR = _total_features_written
FeatureReader_13 [off]
    ATTRIBUTES = GEOTIFF,
    ATTR_ACCUM_MODE = Only Use Result
    COMBINE_GEOM = Use Result
    DATASET = C:\projects\EIRA-data\Data\Piezometer Analysis\01-Basefiles\Topography\demo-topo-clip-reso3_color.tif
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = NONE
    OUTPUT_FEATURES_DISPLAY = Schema and Data Features
    GEOTIFF -> AttributeExposer_7 [off]
AttributeExposer_7 [off]
    ATTR_LIST = fme_dataset
    -> StringReplacer_5 [off]
StringReplacer_5 [off]
    CASE = NO
    FIND_TEXT = C:\projects\EIRA-data\Data\Piezometer Analysis\01-Basefiles\Topography\
    NO_MATCH = _FME_NO_OP_
    REGEXP = NO
    SRC_ATTRS = fme_dataset
    -> StringReplacer_6 [off]
StringReplacer_6 [off]
    CASE = NO
    FIND_TEXT = _raster_edit
    NO_MATCH = _FME_NO_OP_
    REGEXP = NO
    SRC_ATTRS = fme_dataset
    -> StringReplacer_7 [off]
StringReplacer_7 [off]
    CASE = NO
    FIND_TEXT = .tif
    NO_MATCH = _FME_NO_OP_
    REGEXP = NO
    SRC_ATTRS = fme_dataset
    -> WebMapTiler_2 [off]
    -> AttributeCreator_11 [off]
    -> AttributeCreator_12 [off]
WebMapTiler_2 [off]
    INTERPOLATION_TYPE_NAME = Nearest Neighbor
    MAX_ZOOM_LEVEL = 16
    MIN_ZOOM_LEVEL = 1
    NUM_TILES_ATTRIBUTE = _num_tiles
    QUADKEY_ATTRIBUTE = _quadkey
    RASTER_INDEX_ATTRIBUTE = _raster_index
    TILE_COLUMN_ATTRIBUTE = _tile_column
    TILE_ROW_ATTRIBUTE = _tile_row
    TILE_SCHEME = GoogleMapsCompatible
    ZOOM_LEVEL_ATTRIBUTE = _zoom_level
    TILES -> FeatureWriter_15 [Output] [off]
FeatureWriter_15 [off]
    DATASET = C:\projects\EIRA-data\Data\raster_output\topo_clip\@Value(_zoom_level)\@Value(_tile_column)
    DATASET_ATTR = _dataset
    FEATURE_TYPE_LIST_ATTR = _feature_types
    FORMAT = PNGRASTER
    PNGRASTER_COORDINATE_SYSTEM_GRANULARITY = FEATURE
    TOTAL_FEATURES_WRITTEN_ATTR = _total_features_written
FeatureReader_12 [off]
    ATTRIBUTES = GEOTIFF,
    ATTR_ACCUM_MODE = Only Use Result
    COMBINE_GEOM = Use Result
    DATASET = ""C:\projects\EIRA-data\Data\Piezometer Analysis\02-Piezometer Data\Piezo Elev Rasters\Edited\piezo_elev_raster_edit_1_color.tif" "C:\projects\EIRA-data\Data\Piezometer Analysis\02-Piezometer Data\Piezo Elev Rasters\Edited\piezo_elev_raster_edit_2_color.tif" "C:\projects\EIRA-data\Data\Piezometer Analysis\02-Piezometer Data\Piezo Elev Rasters\Edited\piezo_elev_raster_edit_3_color.tif" "C:\projects\EIRA-data\Data\Piezometer Analysis\02-Piezometer Data\Piezo Elev Rasters\Edited\piezo_elev_raster_edit_4_color.tif" "C:\projects\EIRA-data\Data\Piezometer Analysis\02-Piezometer Data\Piezo Elev Rasters\Edited\piezo_elev_raster_edit_5_color.tif" "C:\projects\EIRA-data\Data\Piezometer Analysis\02-Piezometer Data\Piezo Elev Rasters\Edited\piezo_elev_raster_edit_6_color.tif" "C:\projects\EIRA-data\Data\Piezometer Analysis\02-Piezometer Data\Piezo Elev Rasters\Edited\piezo_elev_raster_edit_7_color.tif" "C:\projects\EIRA-data\Data\Piezometer Analysis\02-Piezometer Data\Piezo Elev Rasters\Edited\piezo_elev_raster_edit_8_color.tif" "C:\projects\EIRA-data\Data\Piezometer Analysis\02-Piezometer Data\Piezo Elev Rasters\Edited\piezo_elev_raster_edit_9_color.tif" "C:\projects\EIRA-data\Data\Piezometer Analysis\02-Piezometer Data\Piezo Elev Rasters\Edited\piezo_elev_raster_edit_10_color.tif" "C:\projects\EIRA-data\Data\Piezometer Analysis\02-Piezometer Data\Piezo Elev Rasters\Edited\piezo_elev_raster_edit_11_color.tif" "C:\projects\EIRA-data\Data\Piezometer Analysis\02-Piezometer Data\Piezo Elev Rasters\Edited\piezo_elev_raster_edit_12_color.tif""
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = NONE
    OUTPUT_FEATURES_DISPLAY = Schema and Data Features
    GEOTIFF -> AttributeExposer_6 [off]
AttributeExposer_6 [off]
    ATTR_LIST = fme_dataset
    -> StringReplacer_2 [off]
StringReplacer_2 [off]
    CASE = NO
    FIND_TEXT = C:\projects\EIRA-data\Data\Piezometer Analysis\02-Piezometer Data\Piezo Elev Rasters\Edited\
    NO_MATCH = _FME_NO_OP_
    REGEXP = NO
    SRC_ATTRS = fme_dataset
    -> StringReplacer_3 [off]
StringReplacer_3 [off]
    CASE = NO
    FIND_TEXT = _raster_edit
    NO_MATCH = _FME_NO_OP_
    REGEXP = NO
    SRC_ATTRS = fme_dataset
    -> StringReplacer_4 [off]
StringReplacer_4 [off]
    CASE = NO
    FIND_TEXT = _color.tif
    NO_MATCH = _FME_NO_OP_
    REGEXP = NO
    SRC_ATTRS = fme_dataset
    -> WebMapTiler [off]
    -> AttributeCreator_7 [off]
    -> AttributeCreator_8 [off]
WebMapTiler [off]
    INTERPOLATION_TYPE_NAME = Nearest Neighbor
    MAX_ZOOM_LEVEL = 16
    MIN_ZOOM_LEVEL = 1
    NUM_TILES_ATTRIBUTE = _num_tiles
    QUADKEY_ATTRIBUTE = _quadkey
    RASTER_INDEX_ATTRIBUTE = _raster_index
    TILE_COLUMN_ATTRIBUTE = _tile_column
    TILE_ROW_ATTRIBUTE = _tile_row
    TILE_SCHEME = GoogleMapsCompatible
    ZOOM_LEVEL_ATTRIBUTE = _zoom_level
    TILES -> FeatureWriter_14 [Output] [off]
FeatureWriter_14 [off]
    DATASET = C:\projects\EIRA-data\Data\raster_output\@Value(fme_dataset)\@Value(_zoom_level)\@Value(_tile_column)
    DATASET_ATTR = _dataset
    FEATURE_TYPE_LIST_ATTR = _feature_types
    FORMAT = PNGRASTER
    PNGRASTER_COORDINATE_SYSTEM_GRANULARITY = FEATURE
    TOTAL_FEATURES_WRITTEN_ATTR = _total_features_written
Creator_2 [off]
    GEOMTYPE = Geometry Object
    NUM = 1
    CREATED -> FeatureReader_7 [INITIATOR] [off]
    CREATED -> FeatureReader_8 [INITIATOR] [off]
    CREATED -> FeatureReader_9 [INITIATOR] [off]
    CREATED -> FeatureReader_10 [INITIATOR] [off]
    CREATED -> FeatureReader_11 [INITIATOR] [off]
FeatureReader_7 [off]
    ATTRIBUTES = "Piezo data","Piezometer,Latitude,Longitude,January,February,March,April,May,June,July,August,September,October,November,December"
    ATTR_ACCUM_MODE = Only Use Result
    COMBINE_GEOM = Use Result
    DATASET = C:\projects\EIRA-data\Data\Piezometer Analysis\02-Piezometer Data\Piezo data.shp
    FEATURETYPES = Piezo data
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    Piezo data -> FeatureWriter_9 [Output] [off]
FeatureWriter_9 [off]
    DATASET = C:\projects\EIRA-data\Data\out\piezometer_locations.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
    SUMMARY -> ListExploder [off]
ListExploder [off]
    ATTR_ACCUM_MODE = Merge List Attributes
    ATTR_CONFLICT_RES = Use List Attribute Values
    INDEX_ATTR = _element_index
    LIST_ATTR = _feature_types{}
    ELEMENTS -> AttributeCreator [off]
AttributeCreator [off]
    ATTR_TABLE:
      SET_TO style_json =     {
          "id": "@Value(name)",
          "type": "circle",
          "source": "$(source_id)",
          "source-layer": "@Value(name)",
          "layout": {"visibility": "none"},
          "paint": {
            "circle-radius": 5,
            "circle-stroke-color": "rgba(0, 0, 0, 1)",
            "circle-color": "rgba(255, 255, 255, 1)",
            "circle-stroke-width": 1
          }
        }
    -> Aggregator [off]
FeatureReader_8 [off]
    ATTRIBUTES = EXTENT,"MINX,MINY,MAXX,MAXY,CNTX,CNTY,AREA,PERIM,HEIGHT,WIDTH"
    ATTR_ACCUM_MODE = Only Use Result
    COMBINE_GEOM = Use Result
    DATASET = C:\projects\EIRA-data\Data\Piezometer Analysis\01-Basefiles\EXTENT.shp
    FEATURETYPES = EXTENT
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    EXTENT -> CoordinateSystemSetter [off]
CoordinateSystemSetter [off]
    COORDSYS = EPSG:4326
    -> FeatureWriter_10 [Output] [off]
FeatureWriter_10 [off]
    DATASET = C:\projects\EIRA-data\Data\out\data_extent.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
    SUMMARY -> ListExploder_2 [off]
ListExploder_2 [off]
    ATTR_ACCUM_MODE = Merge List Attributes
    ATTR_CONFLICT_RES = Use List Attribute Values
    INDEX_ATTR = _element_index
    LIST_ATTR = _feature_types{}
    ELEMENTS -> AttributeCreator_2 [off]
AttributeCreator_2 [off]
    ATTR_TABLE:
      SET_TO style_json = {
              "id": "@Value(name)",
              "type": "line",
              "source": "$(source_id)",
              "source-layer": "@Value(name)",
              "layout": {"visibility": "visible"}
            }
    -> Aggregator [off]
FeatureReader_9 [off]
    ATTRIBUTES = "Development Limit",id
    ATTR_ACCUM_MODE = Only Use Result
    COMBINE_GEOM = Use Result
    DATASET = C:\projects\EIRA-data\Data\Piezometer Analysis\01-Basefiles\Development Limit.shp
    FEATURETYPES = Development Limit
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    Development Limit -> CoordinateSystemSetter_2 [off]
CoordinateSystemSetter_2 [off]
    COORDSYS = EPSG:4326
    -> FeatureWriter_11 [Output] [off]
FeatureWriter_11 [off]
    DATASET = C:\projects\EIRA-data\Data\out\approximate_development_limit.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
    SUMMARY -> ListExploder_3 [off]
ListExploder_3 [off]
    ATTR_ACCUM_MODE = Merge List Attributes
    ATTR_CONFLICT_RES = Use List Attribute Values
    INDEX_ATTR = _element_index
    LIST_ATTR = _feature_types{}
    ELEMENTS -> AttributeCreator_3 [off]
AttributeCreator_3 [off]
    ATTR_TABLE:
      SET_TO style_json =
        {
              "id": "@Value(name)",
              "type": "line",
              "source": "$(source_id)",
              "source-layer": "@Value(name)",
              "layout": {"line-join": "round", "visibility": "visible"},
              "paint": {
                "line-color": "#9e9cab",
                "line-dasharray": [3, 1, 1, 1],
                "line-width": {"base": 1.4, "stops": [[4, 0.4], [5, 1], [12, 3]]}
              }
            }
    -> Aggregator [off]
FeatureReader_10 [off]
    ATTRIBUTES = piezo_contour_smooth-1,"ID,ELEV",piezo_contour_smooth-10,"ID,ELEV",piezo_contour_smooth-11,"ID,ELEV",piezo_contour_smooth-12,"ID,ELEV",piezo_contour_smooth-2,"ID,ELEV",piezo_contour_smooth-3,"ID,ELEV",piezo_contour_smooth-4,"ID,ELEV",piezo_contour_smooth-5,"ID,ELEV",piezo_contour_smooth-6,"ID,ELEV",piezo_contour_smooth-7,"ID,ELEV",piezo_contour_smooth-8,"ID,ELEV",piezo_contour_smooth-9,"ID,ELEV"
    ATTR_ACCUM_MODE = Only Use Result
    COMBINE_GEOM = Use Result
    DATASET = ""C:\projects\EIRA-data\Data\Piezometer Analysis\02-Piezometer Data\Piezo Contours\piezo_contour_smooth-1.shp" "C:\projects\EIRA-data\Data\Piezometer Analysis\02-Piezometer Data\Piezo Contours\piezo_contour_smooth-2.shp" "C:\projects\EIRA-data\Data\Piezometer Analysis\02-Piezometer Data\Piezo Contours\piezo_contour_smooth-3.shp" "C:\projects\EIRA-data\Data\Piezometer Analysis\02-Piezometer Data\Piezo Contours\piezo_contour_smooth-4.shp" "C:\projects\EIRA-data\Data\Piezometer Analysis\02-Piezometer Data\Piezo Contours\piezo_contour_smooth-5.shp" "C:\projects\EIRA-data\Data\Piezometer Analysis\02-Piezometer Data\Piezo Contours\piezo_contour_smooth-6.shp" "C:\projects\EIRA-data\Data\Piezometer Analysis\02-Piezometer Data\Piezo Contours\piezo_contour_smooth-7.shp" "C:\projects\EIRA-data\Data\Piezometer Analysis\02-Piezometer Data\Piezo Contours\piezo_contour_smooth-8.shp" "C:\projects\EIRA-data\Data\Piezometer Analysis\02-Piezometer Data\Piezo Contours\piezo_contour_smooth-9.shp" "C:\projects\EIRA-data\Data\Piezometer Analysis\02-Piezometer Data\Piezo Contours\piezo_contour_smooth-10.shp" "C:\projects\EIRA-data\Data\Piezometer Analysis\02-Piezometer Data\Piezo Contours\piezo_contour_smooth-11.shp" "C:\projects\EIRA-data\Data\Piezometer Analysis\02-Piezometer Data\Piezo Contours\piezo_contour_smooth-12.shp""
    FEATURETYPES = piezo_contour_smooth-1 piezo_contour_smooth-2 piezo_contour_smooth-3 piezo_contour_smooth-4 piezo_contour_smooth-5 piezo_contour_smooth-6 piezo_contour_smooth-7 piezo_contour_smooth-8 piezo_contour_smooth-9 piezo_contour_smooth-10 piezo_contour_smooth-11 piezo_contour_smooth-12
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    piezo_contour_smooth-1 -> AttributeExposer_5 [off]
    piezo_contour_smooth-2 -> AttributeExposer_5 [off]
    piezo_contour_smooth-3 -> AttributeExposer_5 [off]
    piezo_contour_smooth-4 -> AttributeExposer_5 [off]
    piezo_contour_smooth-5 -> AttributeExposer_5 [off]
    piezo_contour_smooth-6 -> AttributeExposer_5 [off]
    piezo_contour_smooth-7 -> AttributeExposer_5 [off]
    piezo_contour_smooth-8 -> AttributeExposer_5 [off]
    piezo_contour_smooth-9 -> AttributeExposer_5 [off]
    piezo_contour_smooth-10 -> AttributeExposer_5 [off]
    piezo_contour_smooth-11 -> AttributeExposer_5 [off]
    piezo_contour_smooth-12 -> AttributeExposer_5 [off]
AttributeExposer_5 [off]
    ATTR_LIST = fme_feature_type
    -> StringReplacer [off]
StringReplacer [off]
    CASE = NO
    FIND_TEXT = _smooth
    NO_MATCH = _FME_NO_OP_
    REGEXP = NO
    SRC_ATTRS = fme_feature_type
    -> CoordinateSystemSetter_3 [off]
CoordinateSystemSetter_3 [off]
    COORDSYS = EPSG:4326
    -> AttributeManager [off]
AttributeManager [off]
    ATTR_TABLE:
      RENAME_SET_VALUE ID > id
      RENAME_SET_VALUE ELEV > elevation
    -> FeatureWriter_12 [Output] [off]
FeatureWriter_12 [off]
    DATASET = C:\projects\EIRA-data\Data\out\piezometer_contours.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
    SUMMARY -> ListExploder_4 [off]
ListExploder_4 [off]
    ATTR_ACCUM_MODE = Merge List Attributes
    ATTR_CONFLICT_RES = Use List Attribute Values
    INDEX_ATTR = _element_index
    LIST_ATTR = _feature_types{}
    ELEMENTS -> AttributeCreator_4 [off]
    ELEMENTS -> AttributeCreator_6 [off]
AttributeCreator_4 [off]
    ATTR_TABLE:
      SET_TO style_json = {
              "id": "@Value(name)",
              "type": "line",
              "source": "$(source_id)",
              "source-layer": "@Value(name)",
              "layout": {"visibility": "none"},
              "paint": {
            "line-color": "rgba(2, 25, 255, 1)"
          }
            }
    -> Aggregator [off]
AttributeCreator_6 [off]
    ATTR_TABLE:
      SET_TO style_json =

            {
          "id": "text-@Value(name)",
          "type": "symbol",
          "source": "$(source_id)",
          "source-layer": "@Value(name)",
          "minzoom": 5,
          "layout": {
            "symbol-placement": "line",
            "text-field": "{elevation}",
            "text-font": ["Noto Sans Regular"],
            "text-rotation-alignment": "map",
            "text-size": {
              "base": 1,
              "stops": [[13, 20], [14, 20]]
            },
            "visibility": "none",
            "text-padding": 1,
            "text-allow-overlap": false,
            "text-anchor": "top"
          },
          "paint": {
            "text-color": "#0219FF",
            "text-halo-blur": 0.5,
            "text-halo-width": 1
          }
        }
    -> Aggregator [off]
FeatureReader_11 [off]
    ATTRIBUTES = topo_clipped,"layer_code,length,Elevation,remarks"
    ATTR_ACCUM_MODE = Only Use Result
    COMBINE_GEOM = Use Result
    DATASET = C:\projects\EIRA-data\Data\Piezometer Analysis\01-Basefiles\Topography\topo_clipped.shp
    FEATURETYPES = topo_clipped
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    topo_clipped -> CoordinateSystemSetter_4 [off]
CoordinateSystemSetter_4 [off]
    COORDSYS = EPSG:4326
    -> AttributeManager_2 [off]
AttributeManager_2 [off]
    ATTR_TABLE:
      REMOVE layer_code
      REMOVE length
      RENAME_SET_VALUE Elevation > elevation
    -> FeatureWriter_13 [Output] [off]
FeatureWriter_13 [off]
    DATASET = C:\projects\EIRA-data\Data\out\elevation.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
    SUMMARY -> ListExploder_5 [off]
ListExploder_5 [off]
    ATTR_ACCUM_MODE = Merge List Attributes
    ATTR_CONFLICT_RES = Use List Attribute Values
    INDEX_ATTR = _element_index
    LIST_ATTR = _feature_types{}
    ELEMENTS -> AttributeCreator_5 [off]
AttributeCreator_5 [off]
    ATTR_TABLE:
      SET_TO style_json = {
              "id": "@Value(name)",
              "type": "line",
              "source": "$(source_id)",
              "source-layer": "@Value(name)",
              "layout": {"visibility": "visible"}
            }
    -> Aggregator [off]
Aggregator [off]
    ACCUM_ATTRS_NAME = Drop Incoming Attributes
    AGGREGATE_TYPE = Homogeneous Collection (If Possible)
    CONCAT_ATTRS = style_json
    MODE = Geometry - Assemble One Level
    SEP = ,
Creator_4
    GEOMTYPE = Geometry Object
    NUM = 1
    CREATED -> FeatureReader_15 [INITIATOR]
FeatureReader_15
    ATTRIBUTES = GEOTIFF,
    ATTR_ACCUM_MODE = Only Use Result
    COMBINE_GEOM = Use Result
    DATASET = ""C:\projects\EIRA-data\Data\Piezometer Analysis\04-Output\Ponding Output - reso\Ponding-reso-GIS-1_color.tif" "C:\projects\EIRA-data\Data\Piezometer Analysis\04-Output\Ponding Output - reso\Ponding-reso-GIS-2_color.tif" "C:\projects\EIRA-data\Data\Piezometer Analysis\04-Output\Ponding Output - reso\Ponding-reso-GIS-3_color.tif" "C:\projects\EIRA-data\Data\Piezometer Analysis\04-Output\Ponding Output - reso\Ponding-reso-GIS-4_color.tif" "C:\projects\EIRA-data\Data\Piezometer Analysis\04-Output\Ponding Output - reso\Ponding-reso-GIS-5_color.tif" "C:\projects\EIRA-data\Data\Piezometer Analysis\04-Output\Ponding Output - reso\Ponding-reso-GIS-6_color.tif" "C:\projects\EIRA-data\Data\Piezometer Analysis\04-Output\Ponding Output - reso\Ponding-reso-GIS-7_color.tif" "C:\projects\EIRA-data\Data\Piezometer Analysis\04-Output\Ponding Output - reso\Ponding-reso-GIS-8_color.tif" "C:\projects\EIRA-data\Data\Piezometer Analysis\04-Output\Ponding Output - reso\Ponding-reso-GIS-9_color.tif" "C:\projects\EIRA-data\Data\Piezometer Analysis\04-Output\Ponding Output - reso\Ponding-reso-GIS-10_color.tif" "C:\projects\EIRA-data\Data\Piezometer Analysis\04-Output\Ponding Output - reso\Ponding-reso-GIS-11_color.tif" "C:\projects\EIRA-data\Data\Piezometer Analysis\04-Output\Ponding Output - reso\Ponding-reso-GIS-12_color.tif""
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = NONE
    OUTPUT_FEATURES_DISPLAY = Schema and Data Features
    GEOTIFF -> AttributeExposer_9
AttributeExposer_9
    ATTR_LIST = fme_dataset
    -> StringReplacer_11
StringReplacer_11
    CASE = NO
    FIND_TEXT = C:\projects\EIRA-data\Data\Piezometer Analysis\04-Output\Ponding Output - reso\
    NO_MATCH = _FME_NO_OP_
    REGEXP = NO
    SRC_ATTRS = fme_dataset
    -> StringReplacer_12
StringReplacer_12
    CASE = NO
    FIND_TEXT = -reso-GIS
    NO_MATCH = _FME_NO_OP_
    REGEXP = NO
    SRC_ATTRS = fme_dataset
    -> StringReplacer_13
StringReplacer_13
    CASE = NO
    FIND_TEXT = _color.tif
    NO_MATCH = _FME_NO_OP_
    REGEXP = NO
    SRC_ATTRS = fme_dataset
    -> StringCaseChanger
StringCaseChanger
    ATTRCHOICE = Selected Attributes
    ATTRLIST = fme_dataset
    CHANGE_TYPE = lowercase
    -> StringReplacer_14
StringReplacer_14
    CASE = NO
    FIND_TEXT = -
    NO_MATCH = _FME_NO_OP_
    REGEXP = NO
    REPLACE_TEXT = _
    SRC_ATTRS = fme_dataset
    -> WebMapTiler_4
    -> GeometryRemover
GeometryRemover
    -> AttributeCreator_13
    -> AttributeCreator_14
WebMapTiler_4
    INTERPOLATION_TYPE_NAME = Nearest Neighbor
    MAX_ZOOM_LEVEL = 14
    MIN_ZOOM_LEVEL = 1
    NUM_TILES_ATTRIBUTE = _num_tiles
    QUADKEY_ATTRIBUTE = _quadkey
    RASTER_INDEX_ATTRIBUTE = _raster_index
    TILE_COLUMN_ATTRIBUTE = _tile_column
    TILE_ROW_ATTRIBUTE = _tile_row
    TILE_SCHEME = GoogleMapsCompatible
    ZOOM_LEVEL_ATTRIBUTE = _zoom_level
    TILES -> FeatureWriter_17 [Output]
FeatureWriter_17
    DATASET = C:\projects\EIRA-data\Data\raster_output\@Value(fme_dataset)\@Value(_zoom_level)\@Value(_tile_column)
    DATASET_ATTR = _dataset
    FEATURE_TYPE_LIST_ATTR = _feature_types
    FORMAT = PNGRASTER
    PNGRASTER_COORDINATE_SYSTEM_GRANULARITY = FEATURE
    TOTAL_FEATURES_WRITTEN_ATTR = _total_features_written
Creator_5
    GEOMTYPE = Geometry Object
    NUM = 1
    CREATED -> FeatureReader_16 [INITIATOR]
FeatureReader_16
    ATTRIBUTES = Ponding-vector-1,Pond,Ponding-vector-10,Pond,Ponding-vector-11,Pond,Ponding-vector-12,Pond,Ponding-vector-2,Pond,Ponding-vector-3,Pond,Ponding-vector-4,Pond,Ponding-vector-5,Pond,Ponding-vector-6,Pond,Ponding-vector-7,Pond,Ponding-vector-8,Pond,Ponding-vector-9,Pond
    ATTR_ACCUM_MODE = Only Use Result
    COMBINE_GEOM = Use Result
    DATASET = ""C:\projects\EIRA-data\Data\Ponding Output - vector\Ponding-vector-1.shp" "C:\projects\EIRA-data\Data\Ponding Output - vector\Ponding-vector-2.shp" "C:\projects\EIRA-data\Data\Ponding Output - vector\Ponding-vector-3.shp" "C:\projects\EIRA-data\Data\Ponding Output - vector\Ponding-vector-4.shp" "C:\projects\EIRA-data\Data\Ponding Output - vector\Ponding-vector-5.shp" "C:\projects\EIRA-data\Data\Ponding Output - vector\Ponding-vector-6.shp" "C:\projects\EIRA-data\Data\Ponding Output - vector\Ponding-vector-7.shp" "C:\projects\EIRA-data\Data\Ponding Output - vector\Ponding-vector-8.shp" "C:\projects\EIRA-data\Data\Ponding Output - vector\Ponding-vector-9.shp" "C:\projects\EIRA-data\Data\Ponding Output - vector\Ponding-vector-10.shp" "C:\projects\EIRA-data\Data\Ponding Output - vector\Ponding-vector-11.shp" "C:\projects\EIRA-data\Data\Ponding Output - vector\Ponding-vector-12.shp""
    FEATURETYPES = Ponding-vector-1 Ponding-vector-2 Ponding-vector-3 Ponding-vector-4 Ponding-vector-5 Ponding-vector-6 Ponding-vector-7 Ponding-vector-8 Ponding-vector-9 Ponding-vector-10 Ponding-vector-11 Ponding-vector-12
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    <OTHER> -> AttributeExposer_10
AttributeExposer_10
    ATTR_LIST = fme_feature_type,Pond
    -> StringReplacer_15
StringReplacer_15
    CASE = NO
    FIND_TEXT = Ponding-vector-
    NO_MATCH = _FME_NO_OP_
    REGEXP = NO
    SRC_ATTRS = fme_feature_type
    -> CoordinateSystemSetter_5 [off]
    -> Tester
Tester
    BOOL_OP = OR
    TEST_CLAUSE = TEST @Value(Pond) > 0
    TEST_MODE = TEST
    PASSED -> AttributeManager_3
AttributeManager_3
    ATTR_TABLE = RENAME_SET_VALUE Pond > pond
    -> FeatureWriter_18 [Output]
FeatureWriter_18
    DATASET = C:\projects\EIRA-data\Data\out\ponds.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
CoordinateSystemSetter_5 [off]
    COORDSYS = EPSG:4326
Creator [off]
    GEOMTYPE = Geometry Object
    NUM = 1
    CREATED -> FeatureReader [INITIATOR] [off]
    CREATED -> FeatureReader_2 [INITIATOR] [off]
    CREATED -> FeatureReader_3 [INITIATOR] [off]
    CREATED -> FeatureReader_4 [INITIATOR] [off]
    CREATED -> FeatureReader_5 [INITIATOR] [off]
    CREATED -> FeatureReader_6 [INITIATOR] [off]
FeatureReader [off]
    ATTRIBUTES = pond_contour_apr,Z,pond_contour_aug,Z,pond_contour_dec,Z,pond_contour_feb,Z,pond_contour_jan,Z,pond_contour_jul,Z,pond_contour_jun,Z,pond_contour_mar,Z,pond_contour_may,Z,pond_contour_nov,Z,pond_contour_oct,Z,pond_contour_sept,Z
    ATTR_ACCUM_MODE = Only Use Result
    COMBINE_GEOM = Use Result
    DATASET = ""C:\projects\EIRA-data\Data\Layers\pond_contour_apr.shp" "C:\projects\EIRA-data\Data\Layers\pond_contour_aug.shp" "C:\projects\EIRA-data\Data\Layers\pond_contour_dec.shp" "C:\projects\EIRA-data\Data\Layers\pond_contour_feb.shp" "C:\projects\EIRA-data\Data\Layers\pond_contour_jan.shp" "C:\projects\EIRA-data\Data\Layers\pond_contour_jul.shp" "C:\projects\EIRA-data\Data\Layers\pond_contour_jun.shp" "C:\projects\EIRA-data\Data\Layers\pond_contour_mar.shp" "C:\projects\EIRA-data\Data\Layers\pond_contour_may.shp" "C:\projects\EIRA-data\Data\Layers\pond_contour_nov.shp" "C:\projects\EIRA-data\Data\Layers\pond_contour_oct.shp" "C:\projects\EIRA-data\Data\Layers\pond_contour_sept.shp""
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    pond_contour_apr -> AttributeExposer [off]
    pond_contour_aug -> AttributeExposer [off]
    pond_contour_dec -> AttributeExposer [off]
    pond_contour_feb -> AttributeExposer [off]
    pond_contour_jan -> AttributeExposer [off]
    pond_contour_jul -> AttributeExposer [off]
    pond_contour_jun -> AttributeExposer [off]
    pond_contour_mar -> AttributeExposer [off]
    pond_contour_may -> AttributeExposer [off]
    pond_contour_nov -> AttributeExposer [off]
    pond_contour_oct -> AttributeExposer [off]
    pond_contour_sept -> AttributeExposer [off]
AttributeExposer [off]
    ATTR_LIST = fme_feature_type
    -> AttributeValueMapper [off]
AttributeValueMapper [off]
    LUT = pond_contour_sept,09,pond_contour_oct,10,pond_contour_nov,11,pond_contour_may,05,pond_contour_mar,03,pond_contour_jun,06,pond_contour_jul,07,pond_contour_jan,01,pond_contour_feb,02,pond_contour_dec,12,pond_contour_aug,08,pond_contour_apr,04
    MAPPING_DIRECTION = FORWARD
    SRC = fme_feature_type
    VAL_ATTR = month
    -> FeatureWriter [Output] [off]
FeatureWriter [off]
    DATASET = C:\projects\EIRA-data\Data\out\pond.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
FeatureReader_3 [off]
    ATTRIBUTES = pond_contour_apr,Z,pond_contour_aug,Z,pond_contour_dec,Z,pond_contour_feb,Z,pond_contour_jan,Z,pond_contour_jul,Z,pond_contour_jun,Z,pond_contour_mar,Z,pond_contour_may,Z,pond_contour_nov,Z,pond_contour_oct,Z,pond_contour_sept,Z
    ATTR_ACCUM_MODE = Only Use Result
    COMBINE_GEOM = Use Result
    DATASET = ""C:\projects\EIRA-data\Data\Layers\piezo_contour_apr.shp" "C:\projects\EIRA-data\Data\Layers\piezo_contour_aug.shp" "C:\projects\EIRA-data\Data\Layers\piezo_contour_dec.shp" "C:\projects\EIRA-data\Data\Layers\piezo_contour_feb.shp" "C:\projects\EIRA-data\Data\Layers\piezo_contour_jan.shp" "C:\projects\EIRA-data\Data\Layers\piezo_contour_july.shp" "C:\projects\EIRA-data\Data\Layers\piezo_contour_jun.shp" "C:\projects\EIRA-data\Data\Layers\piezo_contour_mar.shp" "C:\projects\EIRA-data\Data\Layers\piezo_contour_may.shp" "C:\projects\EIRA-data\Data\Layers\piezo_contour_nov.shp" "C:\projects\EIRA-data\Data\Layers\piezo_contour_oct.shp" "C:\projects\EIRA-data\Data\Layers\piezo_contour_sept.shp""
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    <OTHER> -> AttributeExposer_2 [off]
AttributeExposer_2 [off]
    ATTR_LIST = fme_feature_type
    -> AttributeValueMapper_2 [off]
AttributeValueMapper_2 [off]
    LUT = piezo_contour_apr,04,piezo_contour_aug,08,piezo_contour_dec,12,piezo_contour_feb,02,piezo_contour_jan,01,piezo_contour_july,07,piezo_contour_jun,06,piezo_contour_mar,03,piezo_contour_may,05,piezo_contour_nov,11,piezo_contour_oct,10,piezo_contour_sept,09
    MAPPING_DIRECTION = FORWARD
    SRC = fme_feature_type
    VAL_ATTR = month
    -> FeatureWriter_5 [Output] [off]
FeatureWriter_5 [off]
    DATASET = C:\projects\EIRA-data\Data\out\piezo_contours.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
FeatureReader_4 [off]
    ATTRIBUTES = "piezometer locations","name,Latitude,Longitude,Altitude"
    ATTR_ACCUM_MODE = Only Use Result
    COMBINE_GEOM = Use Result
    DATASET = C:\projects\EIRA-data\Data\Layers\piezometer locations.shp
    FEATURETYPES = piezometer locations
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    piezometer locations -> FeatureWriter_6 [Output] [off]
FeatureWriter_6 [off]
    DATASET = C:\projects\EIRA-data\Data\out\piezometer locations.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
FeatureReader_2 [off]
    ATTRIBUTES = world-administrative-boundaries,"french_short,geo_point_2d{},status,name,color_code,continent,region,iso3,iso_3166_1_alpha_2_codes"
    ATTR_ACCUM_MODE = Only Use Result
    COMBINE_GEOM = Use Result
    DATASET = C:\projects\EIRA-data\Data\world-administrative-boundaries.geojson
    FEATURETYPES = world-administrative-boundaries
    FORMAT = GEOJSON
    GEOJSON_FLATTEN_MODE = ALL_LEVELS
    GEOJSON_USE_BASENAME_AS_DEFAULT_FEATURE_TYPE = Yes
    GEOJSON_USE_SEARCH_ENVELOPE = NO
    INTERACT = NONE
    OUTPUT_FEATURES_DISPLAY = Schema and Data Features
    world-administrative-boundaries -> TestFilter [off]
TestFilter [off]
    DEFAULT_VALUE = <UNFILTERED>
    PASSED_TEST_GROUP_OUTPUT = FIRST
    TEST_LIST = "BOOL_OP,OR,COMPOSITE_TEST,""""""1"""""",TEST_CLAUSE,TEST @Value(continent) = Africa",@Value(continent) = Africa
    @Value(continent) = Africa -> FeatureWriter_2 [Output] [off]
    @Value(continent) = Africa -> TestFilter_2 [off]
    @Value(continent) = Africa -> FeatureWriter_3 [Output] [off]
    <UNFILTERED> -> FeatureWriter_2 [Output] [off]
FeatureWriter_2 [off]
    DATASET = C:\projects\EIRA-data\Data\out\countries5.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
FeatureWriter_3 [off]
    DATASET = C:\projects\EIRA-data\Data\out\countries8.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
TestFilter_2 [off]
    DEFAULT_VALUE = <UNFILTERED>
    PASSED_TEST_GROUP_OUTPUT = FIRST
    TEST_LIST = "BOOL_OP,OR,COMPOSITE_TEST,""""""1"""""",TEST_CLAUSE,TEST @Value(name) = Mauritania",Mauritania
    Mauritania -> FeatureWriter_4 [Output] [off]
FeatureWriter_4 [off]
    DATASET = C:\projects\EIRA-data\Data\out\countries12.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
FeatureReader_5 [off]
    ATTRIBUTES = pond_contour_apr,Z,pond_contour_aug,Z,pond_contour_dec,Z,pond_contour_feb,Z,pond_contour_jan,Z,pond_contour_jul,Z,pond_contour_jun,Z,pond_contour_mar,Z,pond_contour_may,Z,pond_contour_nov,Z,pond_contour_oct,Z,pond_contour_sept,Z
    ATTR_ACCUM_MODE = Only Use Result
    COMBINE_GEOM = Use Result
    DATASET = C:\projects\EIRA-data\Data\Layers\topographic contours.shp
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    <OTHER> -> AttributeExposer_3 [off]
AttributeExposer_3 [off]
    ATTR_LIST = fme_feature_type,Elevation
    -> FeatureWriter_7 [Output] [off]
FeatureWriter_7 [off]
    DATASET = C:\projects\EIRA-data\Data\out\topographic _contours.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
FeatureReader_6 [off]
    ATTRIBUTES = pond_contour_apr,Z,pond_contour_aug,Z,pond_contour_dec,Z,pond_contour_feb,Z,pond_contour_jan,Z,pond_contour_jul,Z,pond_contour_jun,Z,pond_contour_mar,Z,pond_contour_may,Z,pond_contour_nov,Z,pond_contour_oct,Z,pond_contour_sept,Z
    ATTR_ACCUM_MODE = Only Use Result
    COMBINE_GEOM = Use Result
    DATASET = C:\projects\EIRA-data\Data\Layers\SRTM contours.shp
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    <OTHER> -> AttributeExposer_4 [off]
AttributeExposer_4 [off]
    ATTR_LIST = fme_feature_type
    -> FeatureWriter_8 [Output] [off]
FeatureWriter_8 [off]
    DATASET = C:\projects\EIRA-data\Data\out\SRTM_contours.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written

Bookmark: New Bookmark
AttributeCreator_9 [off]
    ATTR_TABLE:
      SET_TO json =  "@Value(fme_dataset)_raster": {
              "maxzoom": 22,
              "tileSize": 256,
              "tiles": ["$(url)/raster/topo_@Value(fme_dataset)/{z}/{x}/{y}.png"],
              "type": "raster"
            }
    -> Aggregator_4 [off]
Aggregator_4 [off]
    ACCUM_ATTRS_NAME = Drop Incoming Attributes
    AGGREGATE_TYPE = Homogeneous Collection (If Possible)
    CONCAT_ATTRS = json
    MODE = Geometry - Assemble One Level
    SEP = ",\n"
AttributeCreator_10 [off]
    ATTR_TABLE:
      SET_TO json = {
              "id": "@Value(fme_dataset)",
              "type": "raster",
              "source": "@Value(fme_dataset)_raster",
              "maxzoom": 22,
              "paint": {"raster-opacity": {"base": 1.5, "stops": [[0, 0.6], [6, 0.6]]}},
              "layout": {"visibility": "none"}
            }
    -> Aggregator_5 [off]
Aggregator_5 [off]
    ACCUM_ATTRS_NAME = Drop Incoming Attributes
    AGGREGATE_TYPE = Homogeneous Collection (If Possible)
    CONCAT_ATTRS = json
    MODE = Geometry - Assemble One Level
    SEP = ",\n"

Bookmark: New Bookmark
AttributeCreator_11 [off]
    ATTR_TABLE:
      SET_TO json =  "topo_clip": {
              "maxzoom": 22,
              "tileSize": 256,
              "tiles": ["$(url)/raster/topo_clip/{z}/{x}/{y}.png"],
              "type": "raster"
            }
    -> Aggregator_6 [off]
Aggregator_6 [off]
    ACCUM_ATTRS_NAME = Drop Incoming Attributes
    AGGREGATE_TYPE = Homogeneous Collection (If Possible)
    CONCAT_ATTRS = json
    MODE = Geometry - Assemble One Level
    SEP = ",\n"
AttributeCreator_12 [off]
    ATTR_TABLE:
      SET_TO json = {
              "id": "topo_clip",
              "type": "raster",
              "source": "topo_clip",
              "maxzoom": 22,
              "paint": {"raster-opacity": {"base": 1.5, "stops": [[0, 0.6], [6, 0.6]]}},
              "layout": {"visibility": "none"}
            }
    -> Aggregator_7 [off]
Aggregator_7 [off]
    ACCUM_ATTRS_NAME = Drop Incoming Attributes
    AGGREGATE_TYPE = Homogeneous Collection (If Possible)
    CONCAT_ATTRS = json
    MODE = Geometry - Assemble One Level
    SEP = ",\n"

Bookmark: New Bookmark
AttributeCreator_7 [off]
    ATTR_TABLE:
      SET_TO json =  "@Value(fme_dataset)_raster": {
              "maxzoom": 22,
              "tileSize": 256,
              "tiles": ["$(url)/raster/@Value(fme_dataset)/{z}/{x}/{y}.png"],
              "type": "raster"
            }
    -> Aggregator_2 [off]
Aggregator_2 [off]
    ACCUM_ATTRS_NAME = Drop Incoming Attributes
    AGGREGATE_TYPE = Homogeneous Collection (If Possible)
    CONCAT_ATTRS = json
    MODE = Geometry - Assemble One Level
    SEP = ",\n"
AttributeCreator_8 [off]
    ATTR_TABLE:
      SET_TO json = {
              "id": "@Value(fme_dataset)",
              "type": "raster",
              "source": "@Value(fme_dataset)_raster",
              "maxzoom": 22,
              "paint": {"raster-opacity": {"base": 1.5, "stops": [[0, 0.6], [6, 0.6]]}},
              "layout": {"visibility": "none"}
            }
    -> Aggregator_3 [off]
Aggregator_3 [off]
    ACCUM_ATTRS_NAME = Drop Incoming Attributes
    AGGREGATE_TYPE = Homogeneous Collection (If Possible)
    CONCAT_ATTRS = json
    MODE = Geometry - Assemble One Level
    SEP = ",\n"

Bookmark: New Bookmark
AttributeCreator_13
    ATTR_TABLE:
      SET_TO json =  "@Value(fme_dataset)_raster": {
              "maxzoom": 22,
              "tileSize": 256,
              "tiles": ["$(url)/raster/@Value(fme_dataset)/{z}/{x}/{y}.png"],
              "type": "raster"
            }
    -> Aggregator_8
Aggregator_8
    ACCUM_ATTRS_NAME = Drop Incoming Attributes
    AGGREGATE_TYPE = Homogeneous Collection (If Possible)
    CONCAT_ATTRS = json
    MODE = Geometry - Assemble One Level
    SEP = ",\n"
AttributeCreator_14
    ATTR_TABLE:
      SET_TO json = {
              "id": "@Value(fme_dataset)",
              "type": "raster",
              "source": "@Value(fme_dataset)_raster",
              "maxzoom": 22,
              "paint": {"raster-opacity": {"base": 1.5, "stops": [[0, 0.6], [6, 0.6]]}},
              "layout": {"visibility": "none"}
            }
    -> Aggregator_9
Aggregator_9
    ACCUM_ATTRS_NAME = Drop Incoming Attributes
    AGGREGATE_TYPE = Homogeneous Collection (If Possible)
    CONCAT_ATTRS = json
    MODE = Geometry - Assemble One Level
    SEP = ",\n"
