FME workspace schema.fmw

Creator
    GEOMTYPE = Geometry Object
    NUM = 1
    CREATED -> FeatureReader [INITIATOR]
    CREATED -> FeatureReader_3 [INITIATOR]
FeatureReader_3
    ATTRIBUTES = JSONFeature,"version,name,metadata.maputnik:license,metadata.maputnik:renderer,metadata.openmaptiles:version,sources.pbghis8kc.type,sources.pbghis8kc.tiles{},sources.pbghis8kc.minZoom,sources.pbghis8kc.maxZoom,sources.natural_earth_shaded_relief.maxzoom,sources.natural_earth_shaded_relief.tileSize,sources.natural_earth_shaded_relief.tiles{},sources.natural_earth_shaded_relief.type,sources.hillshade_raster.maxzoom,sources.hillshade_raster.tileSize,sources.hillshade_raster.tiles{},sources.hillshade_raster.type,sources.topo_clip.maxzoom,sources.topo_clip.tileSize,sources.topo_clip.tiles{},sources.topo_clip.type,sources.ponding_2_raster.maxzoom,sources.ponding_2_raster.tileSize,sources.ponding_2_raster.tiles{},sources.ponding_2_raster.type,sources.ponding_3_raster.maxzoom,sources.ponding_3_raster.tileSize,sources.ponding_3_raster.tiles{},sources.ponding_3_raster.type,sources.ponding_4_raster.maxzoom,sources.ponding_4_raster.tileSize,sources.ponding_4_raster.tiles{},sources.ponding_4_raster.type,sources.ponding_5_raster.maxzoom,sources.ponding_5_raster.tileSize,sources.ponding_5_raster.tiles{},sources.ponding_5_raster.type,sources.ponding_6_raster.maxzoom,sources.ponding_6_raster.tileSize,sources.ponding_6_raster.tiles{},sources.ponding_6_raster.type,sources.ponding_7_raster.maxzoom,sources.ponding_7_raster.tileSize,sources.ponding_7_raster.tiles{},sources.ponding_7_raster.type,sources.ponding_8_raster.maxzoom,sources.ponding_8_raster.tileSize,sources.ponding_8_raster.tiles{},sources.ponding_8_raster.type,sources.ponding_9_raster.maxzoom,sources.ponding_9_raster.tileSize,sources.ponding_9_raster.tiles{},sources.ponding_9_raster.type,sources.ponding_10_raster.maxzoom,sources.ponding_10_raster.tileSize,sources.ponding_10_raster.tiles{},sources.ponding_10_raster.type,sources.ponding_11_raster.maxzoom,sources.ponding_11_raster.tileSize,sources.ponding_11_raster.tiles{},sources.ponding_11_raster.type,sources.ponding_12_raster.maxzoom,sources.ponding_12_raster.tileSize,sources.ponding_12_raster.tiles{},sources.ponding_12_raster.type,sources.ponding_1_raster.maxzoom,sources.ponding_1_raster.tileSize,sources.ponding_1_raster.tiles{},sources.ponding_1_raster.type,sources.piezo_elev_2_raster.maxzoom,sources.piezo_elev_2_raster.tileSize,sources.piezo_elev_2_raster.tiles{},sources.piezo_elev_2_raster.type,sources.piezo_elev_3_raster.maxzoom,sources.piezo_elev_3_raster.tileSize,sources.piezo_elev_3_raster.tiles{},sources.piezo_elev_3_raster.type,sources.piezo_elev_4_raster.maxzoom,sources.piezo_elev_4_raster.tileSize,sources.piezo_elev_4_raster.tiles{},sources.piezo_elev_4_raster.type,sources.piezo_elev_5_raster.maxzoom,sources.piezo_elev_5_raster.tileSize,sources.piezo_elev_5_raster.tiles{},sources.piezo_elev_5_raster.type,sources.piezo_elev_6_raster.maxzoom,sources.piezo_elev_6_raster.tileSize,sources.piezo_elev_6_raster.tiles{},sources.piezo_elev_6_raster.type,sources.piezo_elev_7_raster.maxzoom,sources.piezo_elev_7_raster.tileSize,sources.piezo_elev_7_raster.tiles{},sources.piezo_elev_7_raster.type,sources.piezo_elev_8_raster.maxzoom,sources.piezo_elev_8_raster.tileSize,sources.piezo_elev_8_raster.tiles{},sources.piezo_elev_8_raster.type,sources.piezo_elev_9_raster.maxzoom,sources.piezo_elev_9_raster.tileSize,sources.piezo_elev_9_raster.tiles{},sources.piezo_elev_9_raster.type,sources.piezo_elev_10_raster.maxzoom,sources.piezo_elev_10_raster.tileSize,sources.piezo_elev_10_raster.tiles{},sources.piezo_elev_10_raster.type,sources.piezo_elev_11_raster.maxzoom,sources.piezo_elev_11_raster.tileSize,sources.piezo_elev_11_raster.tiles{},sources.piezo_elev_11_raster.type,sources.piezo_elev_12_raster.maxzoom,sources.piezo_elev_12_raster.tileSize,sources.piezo_elev_12_raster.tiles{},sources.piezo_elev_12_raster.type,sources.piezo_elev_1_raster.maxzoom,sources.piezo_elev_1_raster.tileSize,sources.piezo_elev_1_raster.tiles{},sources.piezo_elev_1_raster.type,sprite,glyphs,layers{}.paint.background-color,layers{}.maxzoom,layers{}.paint.raster-opacity.base,layers{}.paint.raster-opacity.stops{}.array{},layers{}.paint.circle-radius,layers{}.paint.circle-stroke-color,layers{}.paint.circle-color,layers{}.paint.circle-stroke-width,layers{}.layout.line-join,layers{}.paint.line-dasharray{},layers{}.paint.line-width.base,layers{}.paint.line-width.stops{}.array{},layers{}.paint.layout.visibility,layers{}.paint.line-color,layers{}.id,layers{}.type,layers{}.source,layers{}.source-layer,layers{}.minzoom,layers{}.layout.symbol-placement,layers{}.layout.text-field,layers{}.layout.text-font{},layers{}.layout.text-rotation-alignment,layers{}.layout.text-size.base,layers{}.layout.text-size.stops{}.array{},layers{}.layout.visibility,layers{}.layout.text-padding,layers{}.layout.text-allow-overlap,layers{}.layout.text-anchor,layers{}.paint.text-color,layers{}.paint.text-halo-blur,layers{}.paint.text-halo-width,id"
    ATTR_ACCUM_MODE = Only Use Result
    COMBINE_GEOM = Use Result
    DATASET = C:\projects\EIRA-data\Data_vector_style\style_raster_background.json
    FEATURETYPES = JSONFeature
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    OUTPUT_FEATURES_DISPLAY = Schema and Data Features
    JSONFeature -> ListExploder_2
ListExploder_2
    ATTR_ACCUM_MODE = Merge List Attributes
    ATTR_CONFLICT_RES = Use List Attribute Values
    INDEX_ATTR = _element_index
    LIST_ATTR = layers{}
    ELEMENTS -> AttributeKeeper
AttributeKeeper
    CREATE_BULK_MODE_FEATURES = NO
    KEEP_ATTRS = id,name,type,source-layer,source
FeatureReader [off]
    ATTRIBUTES = countries,"french_short,geo_point_2d,status,name,color_code,continent,region,iso3,iso_3166_1_alpha_2_codes",piezo_contours,month,"piezometer locations",month,pond,"Z,month"
    ATTR_ACCUM_MODE = Only Use Result
    COMBINE_GEOM = Use Result
    DATASET = ""C:\projects\EIRA-data\Data\webmap\out\countries5.mbtiles" "C:\projects\EIRA-data\Data\webmap\out\countries8.mbtiles" "C:\projects\EIRA-data\Data\webmap\out\countries12.mbtiles" "C:\projects\EIRA-data\Data\webmap\out\piezo_contours.mbtiles" "C:\projects\EIRA-data\Data\webmap\out\piezometer locations.mbtiles" "C:\projects\EIRA-data\Data\webmap\out\pond.mbtiles""
    FORMAT = MBTILES_MVT
    INTERACT = NONE
    MBTILES_MVT_CLIP = YES
    MBTILES_MVT_COORDINATE_SYSTEM_SOURCE = Source Data Bounds
    MBTILES_MVT_QUERY_FEATURE_TYPES_FOR_MERGE_FILTERS = Yes
    MBTILES_MVT_READER_META_ATTRIBUTES = fme_dataset fme_basename
    MBTILES_MVT_READ_BOOLEANS_AS_YES_NO = YES
    MBTILES_MVT_READ_NULLS = YES
    MBTILES_MVT_ZOOM_LEVEL = Maximum
    OUTPUT_FEATURES_DISPLAY = Schema Features
    <SCHEMA> -> ListExploder
ListExploder
    ATTR_ACCUM_MODE = Merge List Attributes
    ATTR_CONFLICT_RES = Use List Attribute Values
    INDEX_ATTR = _element_index
    LIST_ATTR = attribute{}
    ELEMENTS -> AttributeManager
AttributeManager
    ATTR_TABLE:
      REMOVE _creation_instance
      RENAME_SET_VALUE fme_feature_type_name > layer_name
      RENAME_SET_VALUE name > attribute_name
      REMOVE fme_data_type
      REMOVE fme_format_short_name
      REMOVE fme_format_long_name
      REMOVE fme_schema_handling
      REMOVE _element_index
    -> DuplicateFilter
DuplicateFilter
    INPUT_ORDERED_CHOICE = No
    KEYATTR = layer_name
    UNIQUE -> AttributeCreator
AttributeCreator
    ATTR_TABLE = SET_TO month = FME_CONDITIONAL:DEFAULT_VALUE'_FME_NO_OP_'BOOL_OP;OR;COMPOSITE_TEST;1;CASE_INSENSITIVE_TEST @Value(layer_name) CONTAINS 01'January'BOOL_OP;OR;COMPOSITE_TEST;1;CASE_INSENSITIVE_TEST @Value(layer_name) CONTAINS 02'February'BOOL_OP;OR;COMPOSITE_TEST;1;CASE_INSENSITIVE_TEST @Value(layer_name) CONTAINS 03'March'BOOL_OP;OR;COMPOSITE_TEST;1;CASE_INSENSITIVE_TEST @Value(layer_name) CONTAINS 04'April'BOOL_OP;OR;COMPOSITE_TEST;1;CASE_INSENSITIVE_TEST @Value(layer_name) CONTAINS 05'May'BOOL_OP;OR;COMPOSITE_TEST;1;CASE_INSENSITIVE_TEST @Value(layer_name) CONTAINS 06'June'BOOL_OP;OR;COMPOSITE_TEST;1;CASE_INSENSITIVE_TEST @Value(layer_name) CONTAINS 07'July'BOOL_OP;OR;COMPOSITE_TEST;1;CASE_INSENSITIVE_TEST @Value(layer_name) CONTAINS 08'August'BOOL_OP;OR;COMPOSITE_TEST;1;CASE_INSENSITIVE_TEST @Value(layer_name) CONTAINS 09'September'BOOL_OP;OR;COMPOSITE_TEST;1;CASE_INSENSITIVE_TEST @Value(layer_name) CONTAINS 10'October'BOOL_OP;OR;COMPOSITE_TEST;1;CASE_INSENSITIVE_TEST @Value(layer_name) CONTAINS 11'November'BOOL_OP;OR;COMPOSITE_TEST;1;CASE_INSENSITIVE_TEST @Value(layer_name) CONTAINS 12'December'FME_NUM_CONDITIONS13___
    -> AttributeValueMapper
AttributeValueMapper
    LUT = piezometer locations,Piezometer location,countries,Countries,piezo_contours_01,Piezometer contours,piezo_contours_02,Piezometer contours,piezo_contours_03,Piezometer contours,piezo_contours_04,Piezometer contours,piezo_contours_05,Piezometer contours,piezo_contours_06,Piezometer contours,piezo_contours_07,Piezometer contours,piezo_contours_08,Piezometer contours,piezo_contours_09,Piezometer contours,piezo_contours_10,Piezometer contours,piezo_contours_11,Piezometer contours,piezo_contours_12,Piezometer contours,pond_01,Pond,pond_02,Pond,pond_03,Pond,pond_04,Pond,pond_05,Pond,pond_06,Pond,pond_07,Pond,pond_08,Pond,pond_09,Pond,pond_10,Pond,pond_11,Pond,pond_12,Pond
    MAPPING_DIRECTION = FORWARD
    SRC = layer_name
    VAL_ATTR = alias
    -> TestFilter
TestFilter
    DEFAULT_VALUE = <UNFILTERED>
    PASSED_TEST_GROUP_OUTPUT = FIRST
    TEST_LIST = "BOOL_OP,OR,COMPOSITE_TEST,""""""1"""""",TEST_CLAUSE,TEST month ATTRIBUTE_HAS_A_VALUE """,month ATTRIBUTE_HAS_A_VALUE
    month ATTRIBUTE_HAS_A_VALUE -> AttributeCopier
    <UNFILTERED> -> AttributeCopier_2
AttributeCopier
    ATTR_TABLE = COPY alias > group
    MISSING_INPUT_ATTRS = REMOVE
    -> AttributeCreator_2
AttributeCreator_2
    ATTR_TABLE = SET_TO alias = @Value(alias) @Value(month)
    -> Junction
AttributeCopier_2
    ATTR_TABLE = COPY layer_name > group
    MISSING_INPUT_ATTRS = REMOVE
    -> Junction
Junction
    -> AttributeCreator_3
AttributeCreator_3
    ATTR_TABLE = SET_TO active_default = false
    -> AttributeManager_2
AttributeManager_2
    ATTR_TABLE:
      REMOVE month
      REMOVE attribute_name
      REMOVE native_data_type
    -> FeatureWriter [Output]
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(group) = Piezometer contours",@Value(group) = Piezometer contours,"BOOL_OP,OR,COMPOSITE_TEST,""""""1"""""",TEST_CLAUSE,TEST @Value(group) = Pond ",ponds
    @Value(group) = Piezometer contours -> AttributeCreator_5
    ponds -> AttributeCreator_4
AttributeCreator_5
    ATTR_TABLE:
      SET_TO style = {
              "id": "@Value(layer_name)",
              "type": "line",
              "source": "pbghis8kc",
              "source-layer": "@Value(layer_name)",
              "layout": {"visibility": "visible"}
            }
    -> Aggregator
AttributeCreator_4
    ATTR_TABLE:
      SET_TO style = {
              "id": "@Value(layer_name)",
              "type": "fill",
              "source": "pbghis8kc",
              "source-layer": "@Value(layer_name)",
              "layout": {"visibility": "visible"},
              "paint": {
                "fill-color": "rgba(30, 30, 213, 1)",
                "fill-outline-color": "rgba(0, 0, 0, 0.9)"
              }
            }
    -> Aggregator
Aggregator
    ACCUM_ATTRS_NAME = Drop Incoming Attributes
    AGGREGATE_TYPE = Homogeneous Collection (If Possible)
    CONCAT_ATTRS = style
    MODE = Geometry - Assemble One Level
    SEP = ,
FeatureWriter
    DATASET = C:\projects\EIRA-data\Data\webmap\out\layers.json
    DATASET_ATTR = _dataset
    FEATURE_TYPE_LIST_ATTR = _feature_types
    FORMAT = JSON
    JSON_DESTINATION_DATASETTYPE_VALIDATION = Yes
    JSON_INDENT_SIZE = 0
    JSON_MAX_COORDINATE_PRECISION = 10
    JSON_PRETTY_PRINT = YES
    JSON_WRITER_CHARSET = UTF-8
    JSON_WRITE_BOM = No
    JSON_WRITE_FEATURE_TYPE_KEY = NO
    JSON_WRITE_GEOMETRY = NO
    TOTAL_FEATURES_WRITTEN_ATTR = _total_features_written
    SUMMARY -> FeatureReader_2 [INITIATOR]
FeatureReader_2
    ATTRS_TO_EXPOSE = text_line_data
    ATTR_ACCUM_MODE = Only Use Result
    COMBINE_GEOM = Use Result
    DATASET = @Value(_dataset)
    FORMAT = TEXTLINE
    OUTPUT_FEATURES_DISPLAY = Schema and Data Features
    TEXTLINE_CREATE_FEATURE_TABLES_FROM_DATA = Yes
    TEXTLINE_ENCODING = windows-1252
    TEXTLINE_READ_BOTTOM_UP = No
    TEXTLINE_READ_WHOLE_FILE_AT_ONCE = NO
    TEXTLINE_SKIP_FOOTER = 0
    TEXTLINE_SKIP_LINES = 0
    <OTHER> -> StringReplacer
StringReplacer
    CASE = NO
    FIND_TEXT = "false"
    NO_MATCH = _FME_NO_OP_
    REGEXP = NO
    REPLACE_TEXT = false
    SRC_ATTRS = text_line_data
    -> StringReplacer_2
StringReplacer_2
    CASE = NO
    FIND_TEXT = "true"
    NO_MATCH = _FME_NO_OP_
    REGEXP = NO
    REPLACE_TEXT = true
    SRC_ATTRS = text_line_data
    -> FeatureWriter_2 [text_line]
FeatureWriter_2
    DATASET = C:\projects\EIRA-data\Data\webmap\out\layers.json
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
